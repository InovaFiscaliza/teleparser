EricssonASN1 DEFINITIONS IMPLICIT TAGS ::= BEGIN

  CallDataRecord ::= CHOICE
  {
        singleCallDataRecord [0] UMTSGSMPLMNCallDataRecord,
        compositeCallDataRecord [1] CompositeCallDataRecord
  }
END

CompositeCallDataRecord DEFINITIONS IMPLICIT TAGS ::= BEGIN

  CompositeCallDataRecord  ::=  SEQUENCE OF UMTSGSMPLMNCallDataRecord
END

EventModules DEFINITIONS IMPLICIT TAGS ::= BEGIN
 
  EventModule ::= CHOICE
  {
    aoCEventModule               [10] AoCEventModule,
    sSInvocationEventModule      [11] SSIEventModule,
    serviceSwitchEventModule     [12] ServiceSwitchEventModule,
    iNServiceDataEventModule     [16] INServiceDataEventModule,
    chargeRateChangeEventModule  [20] ChargeRateChangeEventModule,
    iSDNSSInvocationEventModule  [23] ISDNSSInvocationEventModule,
    handOverEventModule          [25] HandOverEventModule
  }
END

CallModules DEFINITIONS IMPLICIT TAGS ::= BEGIN

  Transit ::= [0] SET{
    tAC                          [0] TAC OPTIONAL,
    callIdentificationNumber     [1] CallIDNumber OPTIONAL,
    recordSequenceNumber         [2] RecordSequenceNumber OPTIONAL,
    typeOfCallingSubscriber      [3] TypeOfCallingSubscriber OPTIONAL,
    callingPartyNumber           [4] AddressString OPTIONAL,
    calledPartyNumber            [5] AddressString OPTIONAL,
    calledSubscriberIMSI         [6] IMSI OPTIONAL,
    disconnectingParty           [7] DisconnectingParty OPTIONAL,
    dateForStartOfCharge         [8] Date OPTIONAL,
    timeForStartOfCharge         [9] Time OPTIONAL,
    timeForStopOfCharge         [10] Time OPTIONAL,
    chargeableDuration          [11] Time OPTIONAL,
    interruptionTime            [12] Time OPTIONAL,
    timeFromRegisterSeizureToStartOfCharging
                                [13] Time OPTIONAL,
    chargedParty                [14] ChargedParty OPTIONAL,
    originForCharging           [15] ChargingOrigin OPTIONAL,
    tariffClass                 [16] TariffClass OPTIONAL,
    tariffSwitchInd             [17] TariffSwitchInd OPTIONAL,
    numberOfMeterPulses         [18] NumberOfMeterPulses OPTIONAL,
    exchangeIdentity            [19] ExchangeIdentity OPTIONAL,
    mSCIdentification           [20] AddressString OPTIONAL,
    outgoingRoute               [21] Route OPTIONAL,
    incomingRoute               [22] Route OPTIONAL,
    miscellaneousInformation    [23] MiscellaneousInformation OPTIONAL,
    iNMarkingOfMS               [25] INMarkingOfMS OPTIONAL,
    callPosition                [26] CallPosition OPTIONAL,
    eosInfo                     [27] EosInfo OPTIONAL,
    internalCauseAndLoc         [28] InternalCauseAndLoc OPTIONAL,
    originalCalledNumber        [29] AddressString OPTIONAL,
    redirectingNumber           [30] AddressString OPTIONAL,
    redirectionCounter          [31] RedirectionCounter OPTIONAL,
    redirectingDropBackNumber   [32] AddressString OPTIONAL,
    redirectingDropBack         [33] NULL OPTIONAL,
    restartDuringCall           [34] NULL OPTIONAL,
    restartDuringOutputIndicator
                                [35] NULL OPTIONAL,
    iCIOrdered                  [36] NULL OPTIONAL,
    outputForSubscriber         [37] OutputForSubscriber OPTIONAL,
    lastPartialOutput           [38] NULL OPTIONAL,
    partialOutputRecNum         [39] PartialOutputRecNum OPTIONAL,
    relatedCallNumber           [40] CallIDNumber OPTIONAL,
    faultCode                   [41] FaultCode OPTIONAL,
    subscriptionType            [42] SubscriptionType OPTIONAL,
    incompleteCallDataIndicator [43] NULL OPTIONAL,
    incompleteCompositeCDRIndicator
                                [44] NULL OPTIONAL,
    switchIdentity              [45] SwitchIdentity OPTIONAL,
    networkCallReference        [46] NetworkCallReference OPTIONAL,
    disconnectionDueToSystemRecovery
                                [47] NULL OPTIONAL,
    forloppDuringOutputIndicator
                                [48] NULL OPTIONAL,
    forloppReleaseDuringCall    [49] NULL OPTIONAL,
    translatedNumber            [50] AddressString OPTIONAL,
    bCSMTDPData1                [51] CAMELTDPData OPTIONAL,
    bCSMTDPData2                [52] CAMELTDPData OPTIONAL,
    bCSMTDPData3                [53] CAMELTDPData OPTIONAL,
    bCSMTDPData4                [54] CAMELTDPData OPTIONAL,
    bCSMTDPData5                [55] CAMELTDPData OPTIONAL,
    bCSMTDPData6                [56] CAMELTDPData OPTIONAL,
    bCSMTDPData7                [57] CAMELTDPData OPTIONAL,
    bCSMTDPData8                [58] CAMELTDPData OPTIONAL,
    bCSMTDPData9                [59] CAMELTDPData OPTIONAL,
    bCSMTDPData10               [60] CAMELTDPData OPTIONAL,
    gSMCallReferenceNumber      [61] GSMCallReferenceNumber OPTIONAL,
    c7ChargingMessage           [62] C7ChargingMessage OPTIONAL,
    c7FirstCHTMessage           [63] C7CHTMessage OPTIONAL,
    c7SecondCHTMessage          [64] C7CHTMessage OPTIONAL,
    aCMChargingIndicator        [65] ChargingIndicator OPTIONAL,
    aNMChargingIndicator        [66] ChargingIndicator OPTIONAL,
    mSCAddress                  [67] AddressString OPTIONAL,
    carrierInformationBackward  [68] TransitCarrierInfo OPTIONAL,
    carrierInformationForward   [69] TransitCarrierInfo OPTIONAL,
    chargeInformation           [70] ChargeInformation OPTIONAL,
    disconnectionDate           [71] Date OPTIONAL,
    disconnectionTime           [72] Time OPTIONAL,
    entryPOICA                  [73] ChargeAreaCode OPTIONAL,
    exitPOICA                   [74] ChargeAreaCode OPTIONAL,
    internationalCallIndicator  [75] NULL OPTIONAL,
    mobileUserClass1            [76] MobileUserClass1 OPTIONAL,
    mobileUserClass2            [77] MobileUserClass2 OPTIONAL,
    originatingAccessISDN       [78] NULL OPTIONAL,
    originatingCarrier          [79] CarrierInfo OPTIONAL,
    originatingChargeArea       [80] ChargeAreaCode OPTIONAL,
    tDSCounter                  [81] Counter OPTIONAL,
    terminatingAccessISDN       [82] NULL OPTIONAL,
    terminatingCarrier          [83] CarrierInfo OPTIONAL,
    terminatingChargeArea       [84] ChargeAreaCode OPTIONAL,
    terminatingMobileUserClass1 [85] MobileUserClass1 OPTIONAL,
    terminatingMobileUserClass2 [86] MobileUserClass2 OPTIONAL,
    contractorNumber            [87] AddressString OPTIONAL,
    terminatingUserClass        [88] UserClass OPTIONAL,
    userClass                   [89] UserClass OPTIONAL,
    calledPartyMNPInfo          [90] AddressString OPTIONAL,
    chargeNumber                [91] AddressString OPTIONAL,
    originatingLineInformation  [92] OriginatingLineInformation OPTIONAL,
    multimediaInformation       [93] MultimediaInformation OPTIONAL,
    outputType                  [102] OutputType OPTIONAL,
   --F-- originatedCode              [24] OriginatedCode OPTIONAL,
   --F-- reroutingIndicator          [121] NULL OPTIONAL
  }

  MSOriginating ::= [1]SET{
    tAC                          [0] TAC OPTIONAL,
    callIdentificationNumber     [1] CallIDNumber OPTIONAL,
    recordSequenceNumber         [2] RecordSequenceNumber OPTIONAL,
    typeOfCallingSubscriber      [3] TypeOfCallingSubscriber OPTIONAL,
    callingPartyNumber           [4] AddressString OPTIONAL,
    callingSubscriberIMSI        [5] IMSI OPTIONAL,
    callingSubscriberIMEI        [6] IMEI OPTIONAL,
    calledPartyNumber            [7] AddressString OPTIONAL,
    disconnectingParty           [8] DisconnectingParty OPTIONAL,
    dateForStartOfCharge         [9] Date OPTIONAL,
    timeForStartOfCharge        [10] Time OPTIONAL,
    timeForStopOfCharge         [11] Time OPTIONAL,
    chargeableDuration          [12] Time OPTIONAL,
    interruptionTime            [13] Time OPTIONAL,
    timeFromRegisterSeizureToStartOfCharging
                                [14] Time OPTIONAL,
    chargedParty                [15] ChargedParty OPTIONAL,
    originForCharging           [16] ChargingOrigin OPTIONAL,
    chargingCase                [17] ChargingCase OPTIONAL,
    tariffClass                 [18] TariffClass OPTIONAL,
    tariffSwitchInd             [19] TariffSwitchInd OPTIONAL,
    exchangeIdentity            [20] ExchangeIdentity OPTIONAL,
    mSCIdentification           [21] AddressString OPTIONAL,
    outgoingRoute               [22] Route OPTIONAL,
    incomingRoute               [23] Route OPTIONAL,
    miscellaneousInformation    [24] MiscellaneousInformation OPTIONAL,
    originatingLocationNumber   [25] AddressString OPTIONAL,
    timeForTCSeizureCalling     [26] Time OPTIONAL,
    firstCallingLocationInformation
                                [27] LocationInformation OPTIONAL,
    lastCallingLocationInformation
                                [28] LocationInformation OPTIONAL,
    teleServiceCode             [29] TeleServiceCode OPTIONAL,
    bearerServiceCode           [30] BearerServiceCode OPTIONAL,
    transparencyIndicator       [31] TransparencyIndicator OPTIONAL,
    firstRadioChannelUsed       [32] FirstRadioChannelUsed OPTIONAL,
    callPosition                [33] CallPosition OPTIONAL,
    eosInfo                     [34] Eosinfo OPTIONAL,
    internalCauseAndLoc         [35] InternalCauseAndLoc OPTIONAL,
    restartDuringCall           [36] NULL OPTIONAL,
    restartDuringOutputIndicator
                                [37] NULL OPTIONAL,
    numberOfMeterPulses         [38] NumberOfMeterPulses OPTIONAL,
    c7ChargingMessage           [39] C7ChargingMessage OPTIONAL,
    c7FirstCHTMessage           [40] C7CHTMessage OPTIONAL,
    c7SecondCHTMessage          [41] C7CHTMessage OPTIONAL,
    calledPartyMNPInfo          [42] AddressString OPTIONAL,
    carrierIdentificationCode   [43] CarrierIdentificationCode OPTIONAL,
    dTMFUsed                    [44] NULL OPTIONAL,
    iCIOrdered                  [45] NULL OPTIONAL,
    outputForSubscriber         [46] OutputForSubscriber OPTIONAL,
    iNMarkingOfMS               [47] INMarkingOfMS OPTIONAL,
    lastPartialOutput           [48] NULL OPTIONAL,
    partialOutputRecNum         [49] PartialOutputRecNum OPTIONAL,
    cUGInterlockCode            [50] CUGInterlockCode OPTIONAL,
    cUGIndex                    [51] CUGIndex OPTIONAL,
    cUGOutgoingAccessUsed       [52] NULL OPTIONAL,
    cUGOutgoingAccessIndicator  [53] NULL OPTIONAL,
    regionalServiceUsed         [54] RegionalServiceUsed OPTIONAL,
    regionDependentChargingOrigin
                                [55] ChargingOrigin OPTIONAL,
    sSCode                      [56] SSCode OPTIONAL,
    channelAllocationPriorityLevel
                                [57] ChannelAllocationPriorityLevel OPTIONAL,
    radioChannelProperty        [58] RadioChannelProperty OPTIONAL,
    faultCode                   [59] FaultCode OPTIONAL,
    intermediateRate            [60] IntermediateRate OPTIONAL,
    firstAssignedSpeechCoderVersion
                                [61] SpeechCoderVersion OPTIONAL,
    speechCoderPreferenceList   [62] SpeechCoderPreferenceList OPTIONAL,
    subscriptionType            [63] SubscriptionType OPTIONAL,
    incompleteCallDataIndicator
                                [64] NULL OPTIONAL,
    incompleteCompositeCDRIndicator
                                [65] NULL OPTIONAL,
    switchIdentity              [67] SwitchIdentity OPTIONAL,
    networkCallReference        [68] NetworkCallReference OPTIONAL,
    frequencyBandSupported      [69] FrequencyBandSupported OPTIONAL,
    disconnectionDueToSystemRecovery
                                [70] NULL OPTIONAL,
    forloppDuringOutputIndicator
                                [71] NULL OPTIONAL,
    forloppReleaseDuringCall    [72] NULL OPTIONAL,
    accountCode                 [73] AccountCode OPTIONAL,
    translatedNumber            [74] AddressString OPTIONAL,
    bCSMTDPData1                [75] CAMELTDPData OPTIONAL,
    bCSMTDPData2                [76] CAMELTDPData OPTIONAL,
    bCSMTDPData3                [77] CAMELTDPData OPTIONAL,
    bCSMTDPData4                [78] CAMELTDPData OPTIONAL,
    bCSMTDPData5                [79] CAMELTDPData OPTIONAL,
    bCSMTDPData6                [80] CAMELTDPData OPTIONAL,
    bCSMTDPData7                [81] CAMELTDPData OPTIONAL,
    bCSMTDPData8                [82] CAMELTDPData OPTIONAL,
    bCSMTDPData9                [83] CAMELTDPData OPTIONAL,
    bCSMTDPData10               [84] CAMELTDPData OPTIONAL,
    gSMCallReferenceNumber      [85] GSMCallReferenceNumber OPTIONAL,
    mSCAddress                  [86] AddressString OPTIONAL,
    eMLPPPriorityLevel          [87] EMLPPPriorityLevel OPTIONAL,
    positionAccuracy            [88] PositionAccuracy OPTIONAL,
    userTerminalPosition        [89] UserTerminalPosition OPTIONAL,
    acceptableChannelCodings    [90] ChannelCodings OPTIONAL,
    incomingAssignedRoute       [91] Route OPTIONAL,
    channelCodingUsed           [92] ChannelCodings OPTIONAL,
    rANAPCauseCode              [93] RANAPCauseCode OPTIONAL,
    gsmSCFAddress               [94] AddressString OPTIONAL,
    fNURRequested               [95] FixedNetworkUserRate OPTIONAL,
    aIURRequested               [96] AirInterfaceUserRate OPTIONAL,
    numberOfChannelsRequested   [97] NumberOfChannels OPTIONAL,
    bSSMAPCauseCode             [98] BSSMAPCauseCode OPTIONAL,
    multimediaCall              [99] NULL OPTIONAL,
    guaranteedBitRate          [100] BitRate OPTIONAL,
    trafficClass               [101] TrafficClass OPTIONAL,
    outputType                 [102] OutputType OPTIONAL,
    rNCidOfFirstRNC            [103] TargetRNCid OPTIONAL,
    maxBitRateDownlink         [104] BitRate OPTIONAL,
    maxBitRateUplink           [105] BitRate OPTIONAL,
    transferDelay              [106] TransferDelay OPTIONAL,
    deliveryOfErroneousSDU1    [107] DeliveryOfErroneousSDU OPTIONAL,
    deliveryOfErroneousSDU2    [108] DeliveryOfErroneousSDU OPTIONAL,
    deliveryOfErroneousSDU3    [109] DeliveryOfErroneousSDU OPTIONAL,
    residualBitErrorRatio1     [110] ErrorRatio OPTIONAL,
    residualBitErrorRatio2     [111] ErrorRatio OPTIONAL,
    residualBitErrorRatio3     [112] ErrorRatio OPTIONAL,
    sDUErrorRatio1             [113] ErrorRatio OPTIONAL,
    sDUErrorRatio2             [114] ErrorRatio OPTIONAL,
    sDUErrorRatio3             [115] ErrorRatio OPTIONAL,
    aCMChargingIndicator       [116] ChargingIndicator OPTIONAL,
    aNMChargingIndicator       [117] ChargingIndicator OPTIONAL,
    carrierInformationBackward [118] TransitCarrierInfo OPTIONAL,
    chargeInformation          [119] ChargeInformation OPTIONAL,
    disconnectionDate          [120] Date OPTIONAL,
    disconnectionTime          [124] Time OPTIONAL,
    originatingCarrier         [125] CarrierInfo OPTIONAL,
    originatingChargeArea      [126] ChargeAreaCode OPTIONAL,
    tDSCounter                 [127] Counter OPTIONAL,
    terminatingAccessISDN      [128] NULL OPTIONAL,
    terminatingCarrier         [129] CarrierInfo OPTIONAL,
    terminatingChargeArea      [130] ChargeAreaCode OPTIONAL,
    terminatingMobileUserClass1
                               [131] MobileUserClass1 OPTIONAL,
    terminatingMobileUserClass2
                               [132] MobileUserClass2 OPTIONAL,
    terminatingUserClass       [133] UserClass OPTIONAL,
    contractorNumber           [134] AddressString OPTIONAL,
    carrierInformation         [135] CarrierInformation OPTIONAL,
    carrierSelectionSubstitutionInformation
                               [136] CarrierSelectionSubstitutionInformation OPTIONAL,
    chargeNumber               [137] AddressString OPTIONAL,
    interExchangeCarrierIndicator
                               [138] NULL OPTIONAL,
    originatingLineInformation [139] OriginatingLineInformation OPTIONAL,
    selectedCodec              [140] SelectedCodec OPTIONAL,
    wPSCallIndicator           [141] NULL OPTIONAL,
   --F-- originatedCode            [66] OriginatedCode OPTIONAL,
   --F-- reroutingIndicator       [121] NULL OPTIONAL,
   --F-- invocationOfCallHold     [122] NULL OPTIONAL,
   --F-- retrievalOfHeldCall      [123] NULL OPTIONAL
}

END

TaggedData DEFINITIONS IMPLICIT TAGS ::= BEGIN


  UILayerProtocol ::= ENUMERATED 
  {
   v110-X30                     (1),
   g711mulaw                    (2),
   g711Alaw                     (3),
   g721-32000bps-I460           (4),
   h221-H242                    (5),
   h223-H245                    (6),
   nonITU-T                     (7),
   v120                         (8),
   x31                          (9),
   vSELP-Speech                (10)
  }


  UnsuccessfulPositioningDataReason ::= ENUMERATED

  {
   systemError                           (0),
   userDeniedDueToPrivacyVerification    (1)
  }

  UserClass ::= OCTET STRING (SIZE(1))

  UserRate ::= ENUMERATED

    {
    uRIndNeg          (0),
    uR600bps          (1),
    uR1200bps         (2),
    uR2400bps         (3),
    uR3600bps         (4),
    uR4800bps         (5),
    uR7200bps         (6),
    uR8000bps         (7),
    uR9600bps         (8),
    uR14400bps        (9),
    uR16000bps       (10),
    uR19200bps       (11),
    uR32000bps       (12),
    uR38400bps       (13),
    uR48000bps       (14),
    uR56000bps       (15),
    uR64000bps       (16),
    uR38400bps1      (17),
    uR57600bps       (18),
    uR28800bps       (19),
    uR134-5bps       (21),
    uR100bps         (22),
    uR75bps1200bps  (23),
    uR1200bps75bps  (24),
    uR50bps          (25),
    uR75bps          (26),
    uR110bps         (27),
    uR150bps         (28),
    uR200bps         (29),
    uR300bps         (30),
    uR12000bps       (31)
    }
  UserTerminalPosition ::= OCTET STRING (SIZE(7))
  UserToUserService1Information ::= OCTET STRING (SIZE(1))

END
